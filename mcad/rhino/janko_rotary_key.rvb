' Run this file to generate a CAD model of a Janko layout keyboard with rotary keys.
Option Explicit

' Load in necessary libraries and user-defined keyboard parameters.
Rhino.Command("-LoadScript " & Rhino.WorkingFolder & "\libraries\misc.rvb" )
Rhino.Command("-LoadScript " & Rhino.WorkingFolder & "\libraries\geometry.rvb" )
Rhino.Command("-LoadScript " & Rhino.WorkingFolder & "\parameters\five_key_rotary.rvb" )

Call Main()
Sub Main()
	'____________________________________________________________________________________________
	' Compute the locations of the four corners of each key in the X-Y plane.
	' The axis of rotation of the key is taken as the origin. ( The completed key object can be moved later ).
	' Keys are defined to have flat tops, bottoms, and sides, with circular arcs for front and back faces.
	' Row indeces increase towards the back of the keyboard.
	Rhino.Print "Welcome to the diykeyboard.org key generation script"
	Rhino.Print "Starting Main..."

	'Turn off rendering temporarily to speed things up.
	Rhino.EnableRedraw(False)
	
	Rhino.Print "Deleting everything in the document so we can start from scratch..."
	If Not IsNull(Rhino.AllObjects) Then
		Rhino.DeleteObjects(Rhino.AllObjects)
	End If
	
	ReDim topFrontCorners(rowCount - 1)
	ReDim bottomFrontCorners(rowCount - 1)
	ReDim topBackCorners(rowCount - 1)
	ReDim bottomBackCorners(rowCount - 1)

	'Compute the geometry for the first key row.

	topFrontCorners(0) = Array(firstKeyTopFrontX, firstKeyTopFrontY, 0.0)
	topBackCorners(0) = Array(firstKeyTopFrontX - nominalKeyDepth, firstKeyTopFrontY, 0.0)

	bottomFrontCorners(0) = topFrontCorners(0) 'Copy

	' Allow for key travel	
	Call rotate_2D_point_by_angle(bottomFrontCorners(0), -1.0 * KeyTravelAngle, bottomFrontCorners(0))

	'Allow for a ledge of the same height to the bezel as other keys have to the next row.
	Call rotate_2D_point_by_distance(bottomFrontCorners(0), -1.0 * depressedKeyLedge, bottomFrontCorners(0))

	'Allow for our user-selectable additional height
	Call rotate_2D_point_by_distance(bottomFrontCorners(0), -1.0 * frontRowVisibilityDepth, bottomFrontCorners(0))

	bottomBackCorners(0) = topBackCorners(0) ' Copy
	' The bottom back corner of the front key just has to be deep enough that the gap is not visible.
	Call rotate_2D_point_by_distance(bottomBackCorners(0), -1.0 * visibilityDepth, bottomBackCorners(0))

	'Iterate through the rest of the rows, generating geometry
	Dim rowIndex, r
	Dim topFrontCorner, bottomFrontCorner, topBackCorner, bottomBackCorner
	Dim lastTopFrontCorner, lastBottomFrontCorner, lastTopBackCorner, lastBottomBackCorner

	For rowIndex = 2 To rowCount

		'Make the previous four points more accessible.
		lastTopFrontCorner = topFrontCorners(rowIndex - 2)
		lastBottomFrontCorner = bottomFrontCorners(rowIndex - 2)
		lastTopBackCorner = topBackCorners(rowIndex - 2)
		lastBottomBackCorner = bottomBackCorners(rowIndex - 2)

		'topFrontCorner
		Call move_2D_point_radially(lastTopBackCorner, 	-1.0 * radialKeyGap, topFrontCorner)  ' A point on the front surface of the next key.
		Call intersect_line_with_circle2(lastTopBackCorner, lastTopFrontCorner, topFrontCorner, topFrontCorner) ' A point at the right radius, directly behing the last key.
		Call rotate_2D_point_by_distance(topFrontCorner, depressedKeyLedge, topFrontCorner)
		Call rotate_2D_point_by_angle(topFrontCorner, keyTravelAngle, topFrontCorner)

		'topBackCorner
		topBackCorner = topFrontCorner
		topBackCorner(0) = topBackCorner(0) - nominalKeyDepth
		
		'bottomBackCorner
		Call rotate_2D_point_by_distance(topBackCorner, -1.0 * visibilityDepth, bottomBackCorner)
		
		'bottomFrontCorner
		Call move_2D_point_radially(lastBottomBackCorner, -1.0 * radialKeyGap * 0.5, bottomFrontCorner) ' A point halfway into the key gap
		Call intersect_line_with_circle2(lastBottomBackCorner, lastBottomFrontCorner, bottomFrontCorner, bottomFrontCorner)  ' A point halfway in the key gap in line with the last key bottom 
		Call intersect_line_with_circle2(bottomFrontCorner, bottomBackCorner, topFrontCorner, bottomFrontCorner)  ' Now the bottoms of adjacent keys will intersect halfway through the gap.  Smooth!

		topFrontCorners(rowIndex - 1) = topFrontCorner
		bottomFrontCorners(rowIndex - 1) = bottomFrontCorner
		topBackCorners(rowIndex - 1) = topBackCorner
		bottomBackCorners(rowIndex - 1) = bottomBackCorner

	Next

	Rhino.Print "Done Computing Touchpoint geometry..."	

	'____________________________________________________________________________________________
	'Use the previously generated geometry to render the touchpoints.
	Dim frontArc, backArc, topCurve, bottomCurve
	ReDim touchpointArray(rowCount-1)
	For rowIndex = 1 To rowCount

		topFrontCorner = topFrontCorners(rowIndex - 1)
		bottomFrontCorner = bottomFrontCorners(rowIndex - 1)
		topBackCorner = topBackCorners(rowIndex - 1)
		bottomBackCorner = bottomBackCorners(rowIndex - 1)

		'Draw the four bounding curves for the current touchpoint profile.
		topCurve = Rhino.AddLine(topFrontCorner, topBackCorner)
		bottomCurve = Rhino.AddLine(bottomFrontCorner, bottomBackCorner)
		frontArc = add_centered_arc(topFrontCorner, bottomFrontCorner)
		backArc = add_centered_arc(topBackCorner, bottomBackCorner)

		'Perform the extrusion to get our box.
		Dim touchpointExtrusion : touchpointExtrusion = extrude_curve_along_z_symmetric(Array(topCurve, bottomCurve, frontArc, backArc), keyWidth)
		touchpointArray(rowIndex-1) = touchpointExtrusion

	Next
	
	Rhino.Print "Done computing an array of aligned touchpoints!"

	'____________________________________________________________________________________________
	' Draw the key bodies for the even and odd row keys.  Assume that the leftmost key has odd numbered touchpoints (still counting from the bottom)

	Rhino.Print "Starting to compute the geometry for the key bodies..."
	Dim oddRowCount, evenRowCount
	If is_odd(rowCount) Then 'odd number of rows 
		oddRowCount = (rowCount+1) / 2
		evenRowCount = oddRowCount - 1
	Else
		oddRowCount = rowCount / 2
		evenRowCount = rowCount / 2
	End If
	ReDim oddSupportsCurves(0), evenSupportsCurves(0)	

	Dim tempPoint1, tempPoint2, tempPoint3, tempPoint4, tempPoint5, tempPoint6
	Dim originPoint : originPoint = Array(0.0,0.0,0.0)
	
	' Define the point where the supports part of the body curve starts.
	Rhino.Print "Defining the point where the supports part of the body curve starts..."
	Dim supportCurveStartPoint, supportCurveEndPoint
	Call rotate_2D_point_by_angle(bottomFrontCorners(1), -1.0 * keyTravelAngle, supportCurveStartPoint)
	Call rotate_2D_point_by_distance(supportCurveStartPoint, -1.0 * (angularKeyGap + frontKeySupportThickness), supportCurveStartPoint)

	' Draw the part of the body for the first row (odd keys) supports. 
	Rhino.Print "Drawing an oddly shaped support for the first row, odd keys..."
	rowIndex = 1
	Call rotate_2D_point_by_angle(bottomBackCorners(rowIndex - 1), -1.0 * keyTravelAngle, tempPoint2)			
	Call rotate_2D_point_by_distance(tempPoint2, -1.0 * angularKeyGap, tempPoint2)	
	Call rotate_2D_point_by_angle(bottomFrontCorners(rowIndex), -1.0 * keyTravelAngle, tempPoint3)			
	Call rotate_2D_point_by_distance(tempPoint3, -1.0 * angularKeyGap, tempPoint3)	
	Call rotate_2D_point_by_angle(bottomBackCorners(rowIndex), -1.0 * keyTravelAngle, tempPoint4)			
	Call rotate_2D_point_by_distance(tempPoint4, -1.0 * angularKeyGap, tempPoint4)	
	Call rotate_2D_point_by_angle(bottomFrontCorners(rowIndex+1), -1.0 * keyTravelAngle, tempPoint5)			
	Call rotate_2D_point_by_distance(tempPoint5, -1.0 * angularKeyGap, tempPoint5)	

	oddSupportsCurves(0) = Rhino.AddLine(supportCurveStartPoint, bottomFrontCorners(0)) ' Line
	Call add_element_to_array(oddSupportsCurves, Rhino.AddLine(bottomFrontCorners(0), bottomBackCorners(0))) 'Line
	Call add_element_to_array(oddSupportsCurves, add_centered_arc(bottomBackCorners(0), tempPoint2)) 'Arc
	Call add_element_to_array(oddSupportsCurves, Rhino.AddLine(tempPoint2, tempPoint3)) 'Line
	Call add_element_to_array(oddSupportsCurves, Rhino.AddLine(tempPoint3, tempPoint4)) 'Line
	Call add_element_to_array(oddSupportsCurves, Rhino.AddLine(tempPoint4, tempPoint5)) 'Line


	' Add the little arc to get the second row support up to the canonical support position.
	Call rotate_2D_point_by_angle(bottomFrontCorners(1), -1.0 * keyTravelAngle, tempPoint1)
	Call rotate_2D_point_by_distance(tempPoint1, -1.0 * angularKeyGap, tempPoint1)
	evenSupportsCurves(0) = add_centered_arc(supportCurveStartPoint, tempPoint1)

	' Draw the normal supports, starting from the second row, starting from the second row.
	Rhino.Print "Starting to draw the normal touchpoint supports..."
	For rowIndex = 2 To (rowCount - 2)

		Call rotate_2D_point_by_angle(bottomFrontCorners(rowIndex - 1), -1.0 * keyTravelAngle, tempPoint1)
		Call rotate_2D_point_by_distance(tempPoint1, -1.0 * angularKeyGap, tempPoint1)	
		Call rotate_2D_point_by_angle(bottomBackCorners(rowIndex - 1), -1.0 * keyTravelAngle, tempPoint2)			
		Call rotate_2D_point_by_distance(tempPoint2, -1.0 * angularKeyGap, tempPoint2)	
		Call rotate_2D_point_by_angle(bottomFrontCorners(rowIndex), -1.0 * keyTravelAngle, tempPoint3)			
		Call rotate_2D_point_by_distance(tempPoint3, -1.0 * angularKeyGap, tempPoint3)	
		Call rotate_2D_point_by_angle(bottomBackCorners(rowIndex), -1.0 * keyTravelAngle, tempPoint4)			
		Call rotate_2D_point_by_distance(tempPoint4, -1.0 * angularKeyGap, tempPoint4)	
		Call rotate_2D_point_by_angle(bottomFrontCorners(rowIndex+1), -1.0 * keyTravelAngle, tempPoint5)			
		Call rotate_2D_point_by_distance(tempPoint5, -1.0 * angularKeyGap, tempPoint5)	

		If is_odd(rowIndex) Then
			Call add_element_to_array(oddSupportsCurves, add_centered_arc(tempPoint1, bottomFrontCorners(rowIndex - 1)))
			Call add_element_to_array(oddSupportsCurves, Rhino.AddLine(bottomFrontCorners(rowIndex - 1), bottomBackCorners(rowIndex - 1)))
			Call add_element_to_array(oddSupportsCurves, add_centered_arc(bottomBackCorners(rowIndex - 1), tempPoint2))
			Call add_element_to_array(oddSupportsCurves, Rhino.AddLine(tempPoint2, tempPoint3))
			Call add_element_to_array(oddSupportsCurves, Rhino.AddLine(tempPoint3, tempPoint4))
			Call add_element_to_array(oddSupportsCurves, Rhino.AddLine(tempPoint4, tempPoint5))

		Else
			Call add_element_to_array(evenSupportsCurves, add_centered_arc(tempPoint1, bottomFrontCorners(rowIndex - 1)))
			Call add_element_to_array(evenSupportsCurves, Rhino.AddLine(bottomFrontCorners(rowIndex - 1), bottomBackCorners(rowIndex - 1)))
			Call add_element_to_array(evenSupportsCurves, add_centered_arc(bottomBackCorners(rowIndex - 1), tempPoint2))
			Call add_element_to_array(evenSupportsCurves, Rhino.AddLine(tempPoint2, tempPoint3))
			Call add_element_to_array(evenSupportsCurves, Rhino.AddLine(tempPoint3, tempPoint4))
			Call add_element_to_array(evenSupportsCurves, Rhino.AddLine(tempPoint4, tempPoint5))
		End If

	Next

	' Compute the geometry of the last couple rows.
	Rhino.Print "Starting to draw the touchpoint supports for the last couple rows..." 

	' The second to last row starts the same as the other rows, but misses the last little line.
	rowIndex = rowCount - 1
	Call rotate_2D_point_by_angle(bottomFrontCorners(rowIndex - 1), -1.0 * keyTravelAngle, tempPoint1)
	Call rotate_2D_point_by_distance(tempPoint1, -1.0 * angularKeyGap, tempPoint1)	
	Call rotate_2D_point_by_angle(bottomBackCorners(rowIndex - 1), -1.0 * keyTravelAngle, tempPoint2)			
	Call rotate_2D_point_by_distance(tempPoint2, -1.0 * angularKeyGap, tempPoint2)	
	Call rotate_2D_point_by_angle(bottomFrontCorners(rowIndex), -1.0 * keyTravelAngle, tempPoint3)			
	Call rotate_2D_point_by_distance(tempPoint3, -1.0 * angularKeyGap, tempPoint3)	
	'	Call rotate_2D_point_by_angle(bottomBackCorners(rowIndex), -1.0 * keyTravelAngle, tempPoint4)			
	'	Call rotate_2D_point_by_distance(tempPoint4, -1.0 * angularKeyGap, tempPoint4)	
	If is_odd(rowIndex) Then
		Call add_element_to_array(oddSupportsCurves, add_centered_arc(tempPoint1, bottomFrontCorners(rowIndex - 1)))
		Call add_element_to_array(oddSupportsCurves, Rhino.AddLine(bottomFrontCorners(rowIndex - 1), bottomBackCorners(rowIndex - 1)))
		Call add_element_to_array(oddSupportsCurves, add_centered_arc(bottomBackCorners(rowIndex - 1), tempPoint2))
		Call add_element_to_array(oddSupportsCurves, Rhino.AddLine(tempPoint2, tempPoint3))
		'		Call add_element_to_array(oddSupportsCurves, Rhino.AddLine(tempPoint3, tempPoint4))
	Else
		Call add_element_to_array(evenSupportsCurves, add_centered_arc(tempPoint1, bottomFrontCorners(rowIndex - 1)))
		Call add_element_to_array(evenSupportsCurves, Rhino.AddLine(bottomFrontCorners(rowIndex - 1), bottomBackCorners(rowIndex - 1)))
		Call add_element_to_array(evenSupportsCurves, add_centered_arc(bottomBackCorners(rowIndex - 1), tempPoint2))
		Call add_element_to_array(evenSupportsCurves, Rhino.AddLine(tempPoint2, tempPoint3))
		'		Call add_element_to_array(evenSupportsCurves, Rhino.AddLine(tempPoint3, tempPoint4))
	End If

	'Some geometry for the last bits of the last two rows
	rowIndex = rowCount
	Call rotate_2D_point_by_angle(bottomFrontCorners(rowIndex - 1), -1.0 * keyTravelAngle, tempPoint1)
	Call rotate_2D_point_by_distance(tempPoint1, -1.0 * angularKeyGap, tempPoint1)	

	Call rotate_2D_point_by_angle(bottomBackCorners(rowIndex - 1), -1.0 * keyTravelAngle, tempPoint2)			
	Call rotate_2D_point_by_distance(tempPoint2, -1.0 * angularKeyGap, tempPoint2)	

	Call move_2D_point_radially(tempPoint2, -1.0 * radialKeyGap, tempPoint3) ' Get a point with radius of tempPoint3.
	Call intersect_line_with_circle2(tempPoint1, tempPoint2, tempPoint3, tempPoint3) ' Move it in line with tempPoint1, tempPoint2, preserving radius

	Call move_2D_point_radially(topBackCorners(rowIndex - 1), -1.0 * radialKeyGap, tempPoint4)
	Call move_2D_point_radially(topBackCorners(rowIndex - 1), -1.0 * radialKeyGap - guideSupportDepth, tempPoint5)

	Call rotate_2D_point_by_angle(tempPoint5, -1.0 * keyTravelAngle, tempPoint6)			
	Call rotate_2D_point_by_distance(tempPoint6, -1.0 * angularKeyGap, tempPoint6)	
	
	If is_odd(rowCount) Then ' If odd number of rows, the second-to-last row is even.

		' Draw the extra bit of support for the second-to-last row.  It has a small un-supported-looking sliver.
		Call add_element_to_array(evenSupportsCurves, Rhino.AddLine(tempPoint1, tempPoint3))
		Call add_element_to_array(evenSupportsCurves, add_centered_arc(tempPoint3, tempPoint4))
		Call add_element_to_array(evenSupportsCurves, Rhino.AddLine(tempPoint4, tempPoint5))
		Call add_element_to_array(evenSupportsCurves, add_centered_arc(tempPoint5, tempPoint6))

		' Draw the weird support for the last row.  The little body-width sliver is supported.
		Call add_element_to_array(oddSupportsCurves, add_centered_arc(tempPoint1, bottomFrontCorners(rowCount - 1)))
		Call add_element_to_array(oddSupportsCurves, Rhino.AddLine(bottomFrontCorners(rowCount - 1), bottomBackCorners(rowCount - 1)))
		Call add_element_to_array(oddSupportsCurves, add_centered_arc(bottomBackCorners(rowCount - 1), topBackCorners(rowCount - 1)))
		Call add_element_to_array(oddSupportsCurves, Rhino.AddLine(topBackCorners(rowCount - 1), tempPoint5))
		Call add_element_to_array(oddSupportsCurves, add_centered_arc(tempPoint5, tempPoint6))

	Else
		' Draw the extra bit of support for the second-to-last row.  It has a small un-supported-looking sliver.
		Call add_element_to_array(oddSupportsCurves, Rhino.AddLine(tempPoint1, tempPoint3))
		Call add_element_to_array(oddSupportsCurves, add_centered_arc(tempPoint3, tempPoint4))
		Call add_element_to_array(oddSupportsCurves, Rhino.AddLine(tempPoint4, tempPoint5))
		Call add_element_to_array(oddSupportsCurves, add_centered_arc(tempPoint5, tempPoint6))

		' Draw the weird support for the last row.  The little body-width sliver is supported.
		Call add_element_to_array(evenSupportsCurves, add_centered_arc(tempPoint1, bottomFrontCorners(rowCount - 1)))
		Call add_element_to_array(evenSupportsCurves, Rhino.AddLine(bottomFrontCorners(rowCount - 1), bottomBackCorners(rowCount - 1)))
		Call add_element_to_array(evenSupportsCurves, add_centered_arc(bottomBackCorners(rowCount - 1), topBackCorners(rowCount - 1)))
		Call add_element_to_array(evenSupportsCurves, Rhino.AddLine(topBackCorners(rowCount - 1), tempPoint5))
		Call add_element_to_array(evenSupportsCurves, add_centered_arc(tempPoint5, tempPoint6))

	End If
	supportCurveEndPoint = tempPoint6

	' Complete the key body curve.
	Rhino.Print "Completing the curves for the key bodies..."
	Dim oddKeyBodyCurves : oddKeyBodyCurves = oddSupportsCurves
	Dim evenKeyBodyCurves : evenKeyBodyCurves = evenSupportsCurves

	'Placeholder:  Just connect start and end to the originwith a line.
	Call add_element_to_array(oddKeyBodyCurves, Rhino.AddLine(supportCurveEndPoint, originPoint))
	Call add_element_to_array(oddKeyBodyCurves, Rhino.AddLine(originPoint, supportCurveStartPoint))
	Call add_element_to_array(evenKeyBodyCurves, Rhino.AddLine(supportCurveEndPoint, originPoint))
	Call add_element_to_array(evenKeyBodyCurves, Rhino.AddLine(originPoint, supportCurveStartPoint))
	
	' Extrude the key bodies out into 3D
	Dim oddKeyBodyExtrusion : oddKeyBodyExtrusion = extrude_curve_along_z_symmetric(oddKeyBodyCurves, keyBodyWidth)		
	Dim evenKeyBodyExtrusion : evenKeyBodyExtrusion = extrude_curve_along_z_symmetric(evenKeyBodyCurves, keyBodyWidth)		

	' Union the odd and even key tops with their respective key bodies
	Dim evenKeySolid, oddKeySolid
	oddKeySolid = oddKeyBodyExtrusion
	evenKeySolid = evenKeyBodyExtrusion
	Dim tempArray
	For rowIndex = 1 To rowCount
		If is_even(rowIndex) Then			
			tempArray = Rhino.BooleanUnion(Array(touchpointArray(rowIndex-1), evenKeySolid))
			evenKeySolid = tempArray(0)			
		Else
			tempArray = Rhino.BooleanUnion(Array(touchpointArray(rowIndex-1), oddKeySolid))
			oddKeySolid = tempArray(0)			
		End If
	Next

	' Move the even key out one nominal key spacing.
	Call Rhino.MoveObject(evenKeySolid, Array(0.0,0.0,0.0), Array(0.0,0.0,nominalKeyWidth * 0.5))

	' Tesselate the keys so that we have one module's worth.
	ReDim evenKeySolids(keysPerModule/2 - 1)
	ReDim oddKeySolids(keysPerModule/2 - 1)
	Dim copyIndex
	For copyIndex = 1 To keysPerModule/2
		evenKeySolids(copyIndex - 1) = Rhino.CopyObject(evenKeySolid, Array(0.0,0.0,0.0), Array(0.0,0.0,nominalKeyWidth * (copyIndex - 1)))
		oddKeySolids(copyIndex - 1)  = Rhino.CopyObject(oddKeySolid,  Array(0.0,0.0,0.0), Array(0.0,0.0,nominalKeyWidth * (copyIndex - 1)))
	Next

	'Depress a couple of the keys to check gaps and visualize ergonomics
	'If there are four or more keys, rotate the third key, which is the second odd key, index 1.
	If keysPerModule > 3 Then
		Call Rhino.RotateObject(oddKeySolids(1), Array(0.0,0.0,0.0), -1.0 * keyTravelAngle * 180 / Rhino.Pi, Array(0.0,0.0,1.0))
	End If
	'If there are seven or more keys, rotate the sixth key, which is the third even key, index 2.
	If keysPerModule > 5 Then
		Call Rhino.RotateObject(evenKeySolids(2), Array(0.0,0.0,0.0), -1.0 * keyTravelAngle * 180 / Rhino.Pi, Array(0.0,0.0,1.0))
	End If


	'____________________________________________________________________________________________
	' Generate key guides.
	' Hopefully one part can double as the fulcrum base, as well as upper and lower-front key guides.
	'Redim keyGuideTeethCurves(0)

	'For copyIndex = 1 To keysPerModule	 ' Iterate through keys.
		' Draw a tooth.
	'	Call add_element_to_array(keyGuideTeethCurves, Rhino.AddLine(bottomFrontCorners(0), bottomBackCorners(0))) 'Line
	
	'Next



	'____________________________________________________________________________________________
	' Go ahead and render everything

	Rhino.Print "Model is ready for display..."

	' Rotate the entire model so that it is easier to view
'	Call Rhino.RotateObjects(Array(evenKeySolid, oddKeySolid), Array(0.0,0.0,0.0), 90 , Array(1.0,0.0,0.0))
	Call Rhino.RotateObjects(Rhino.AllObjects, Array(0.0,0.0,0.0), 90 , Array(1.0,0.0,0.0))

	Call Rhino.ShowGrid(Rhino.CurrentView, False)
	Call Rhino.ShowGridAxes(Rhino.CurrentView, False)
	Call Rhino.ShowWorldAxes(Rhino.CurrentView, False)

	'Turn rendering back on.
	Call Rhino.ZoomExtents(Rhino.CurrentView,True) ' Zoom all views to object extents
	'Set the rendering mode to shaded
	Dim arrViews, strView
	arrViews = Rhino.ViewNames
	If IsArray(arrViews) Then
		For Each strView In arrViews
			Rhino.ViewDisplayMode strView, 1
		Next
	End If

	Call Rhino.EnableRedraw(True)
	
	Rhino.Print "Got to the end of Main!"
End Sub
