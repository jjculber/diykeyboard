' This is where users can tweak the parameters of the keyboard that is generated by janko_rotary_key

'______________________'Major Parameters.  Stuff that defines the basic geometry of the keys. ______________________
Dim rowCount : rowCount = 6 '  The total number of rows.
Dim keysPerModule : keysPerModule = 8 '  The number of keys per module.  Must be even.
Dim octaveSpacing : octaveSpacing = 167.0 'mm  The center-to-center span of an octave.  170mm is Yamaha 5-7 spacing.
Dim nominalKeyWidth : nominalKeyWidth = octaveSpacing / 6.0 'mm  The Width of a key, including a key's worth of gap between keys
Dim nominalKeyDepth : nominalKeyDepth = 25.0 'mm  The Depth of a key, not counting the gap between keys
Dim keyTravelAngle : keyTravelAngle = 4.0 * Rhino.Pi / 180.0 'radians  The angle the key travels through before bottoming out.
Dim depressedKeyLedge : depressedKeyLedge = 1.0 'mm.  The approximate height difference between the front of a depressed key and the next un-depressed key row.  Affects the ergonomics of chord slides.
Dim firstKeyTopFrontX : firstKeyTopFrontX = 300.0 'mm.  The location of the lowest (frontmost) key corner.
Dim firstKeyTopFrontY : firstKeyTopFrontY = -10.0 'mm.  The location of the lowest (frontmost) key corner.


'______________________ Minor Parameters.  Stuff that doesn't really affect the ergonomics of the piano. ___________________________
Dim radialKeyGap : radialKeyGap = 2.0 'mm  The gap between keys expressed as a change of Radius.
Dim lateralKeyGap : lateralKeyGap = 2.0 'mm The sideways gab between keys
Dim angularKeyGap : angularKeyGap = 3.0 'mm The gap between the bottom of a touchpoint and the adjacent key body when depressed.
'Dim filletRadius : filletRadius = 1.0 'mm  The radius of the fillet on most key surfaces.
Dim visibilityDepth : visibilityDepth = 20.0 'mm Approximately how far bottom front of keys extend below the next lower row when lower row is depressed.
Dim frontRowVisibilityDepth : frontRowVisibilityDepth = 30.0 'mm  Like VisibilityDepth, but can be set appropriately for the front bezel.

Dim frontKeySupportThickness : frontKeySupportThickness = 15.0 'mm The height of the narrow part of the support for the front (odd numbered) keys. 

Dim guideFeltThickness : guideFeltThickness = 4.0 ' The thickness of the felt that stabilizes the keys.
Dim upperStopFeltThickness : upperStopFeltThickness = 4.0 ' The theckness of the felt that stops the keys at the top of key travel.
Dim lowerStopFeltThickness : lowerStopFeltThickness = 6.0 ' The theckness of the felt that stops the keys at the bottom of key travel.
Dim tineToTrackRatio : tineToTrackRatio = 0.4 ' The ratio between the key guide tine thickness and the guide track thickness.
Dim guideSupportDepth : guideSupportDepth = 8.0 ' mm The radial depth of the key body width support for the track.  

'______________________ Derived Parameters.  Stuff that is computed from the major and minor parameters. ___________________________

Dim keyBodyWidth : keyBodyWidth = nominalKeyWidth * 0.5 - lateralKeyGap ' The width between keys at the key body.
Dim halfKeyBodyWidth : halfKeyBodyWidth = keyBodyWidth * 0.5
Dim keyGuideTrackWidth : keyGuideTrackWidth = (nominalKeyWidth * 0.5 - 2 * guideFeltThickness) * tineToTrackRatio ' Width of the guide track on the key.
Dim keyGuideTineWidth : keyGuideTineWidth = (nominalKeyWidth * 0.5 - 2 * guideFeltThickness) * (1 - tineToTrackRatio) ' Width of the tine on the (stationary) key guide.
Dim keyWidth : keyWidth = nominalKeyWidth - lateralKeyGap  ' The width of the touchpoint part of the key
Dim halfKeyWidth : halfKeyWidth = keyWidth * 0.5
