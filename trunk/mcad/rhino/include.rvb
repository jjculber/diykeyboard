' ---------------------------------------------------------------------------
' Subroutine:  Include
' Purpose:     Includes, or loads, other RhinoScript files
' Argument:    A script file name to include
' Example:     Include "C:\Scripts\MyScriptFile.rvb"
' ---------------------------------------------------------------------------
Public Function Include (strScriptName)
	Dim oFS, oFile
	Set oFS = CreateObject("Scripting.FileSystemObject")
	Set oFile = oFS.OpenTextFile(strScriptName)
	ExecuteGlobal oFile.ReadAll()
	oFile.Close
	Include = Null
End Function
